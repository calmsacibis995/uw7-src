--ident	"@(#)hpnp.mib	1.2"

HP-MIB { iso org(3) dod(6) internet(1) private(4) enterprises(1) 11 }

DEFINITIONS ::= BEGIN

IMPORTS
     private, enterprises, Counter, Gauge, TimeTicks, NetworkAddress
          FROM RFC1065-SMI;
hp                  OBJECT IDENTIFIER ::= { enterprises 11 }
nm                  OBJECT IDENTIFIER ::= { hp 2 }
system              OBJECT IDENTIFIER ::= { nm 3 }
interface           OBJECT IDENTIFIER ::= { nm 4 }
snmp                OBJECT IDENTIFIER ::= { nm 13 }
net_peripheral      OBJECT IDENTIFIER ::= { system 9 }
net_printer         OBJECT IDENTIFIER ::= { net_peripheral 1 }
generalDeviceStatus OBJECT IDENTIFIER ::= { net_printer 1 }
ieee8023Mac         OBJECT IDENTIFIER ::= { interface 1 }
--- ieee8025Mac     OBJECT IDENTIFIER ::= { interface 2 }
npCard              OBJECT IDENTIFIER ::= { interface 3 }
trap                OBJECT IDENTIFIER ::= { snmp 1 }
npSys               OBJECT IDENTIFIER ::= { npCard 1 }
npNpi               OBJECT IDENTIFIER ::= { npCard 2 }
npElt               OBJECT IDENTIFIER ::= { npCard 3 }
npConns             OBJECT IDENTIFIER ::= { npCard 4 }
npCfg               OBJECT IDENTIFIER ::= { npCard 5 }
npTcp               OBJECT IDENTIFIER ::= { npCard 6 }
npCtl               OBJECT IDENTIFIER ::= { npCard 7 }


-- object types

-- The Status Group

gdStatusBytes OBJECT-TYPE
    SYNTAX  INTEGER
    ACCESS  read-only
    STATUS  optional
    DESCRIPTION
        "The number of valid bytes in the gdStatusEntry
         array."
    ::={ generalDeviceStatus 1 }

gdStatusEntry OBJECT-TYPE
    SYNTAX  GdStatusEntry
    ACCESS  read-only
    STATUS  optional
    DESCRIPTION
        "The networked peripheral's 32 octet status
         information that is shared between the peripheral
         and the LAN card."
    ::={ generalDeviceStatus 2 }

GdStatusEntry ::=
    SEQUENCE {
        gdStatusLineState
            INTEGER,
        gdStatusPaperState
            INTEGER,
        gdStatusInterventionState
            INTEGER,
        gdStatusNewMode
            INTEGER,
        gdStatusConnectionTerminationAck
            INTEGER,
        gdStatusPeripheralError
            INTEGER,
        gdStatusIoChannelReset
            INTEGER,
        gdStatusPaperOut
            INTEGER,
        gdStatusPaperJam
            INTEGER,
        gdStatusTonerLow
            INTEGER,
        gdStatusPagePunt
            INTEGER,
        gdStatusMemoryOut
            INTEGER,
        gdStatusIoActive
            INTEGER,
        gdStatusBusy
            INTEGER,
        gdStatusWait
            INTEGER,
        gdStatusInitialize
            INTEGER,
        gdStatusDoorOpen
            INTEGER,
        gdStatusPrinting
            INTEGER,
        gdStatusPaperOutput
            INTEGER,
        gdStatusReserved
            OCTET STRING
}

gdStatusLineState OBJECT-TYPE
    SYNTAX  INTEGER (0..255)
    ACCESS  read-only
    STATUS  optional
    DESCRIPTION
        "This describes the line state of the peripheral.
         When non-zero, the peripheral is off-line.  When
         zero the peripheral is on-line."
    ::={ gdStatusEntry 1 }

gdStatusPaperState OBJECT-TYPE
    SYNTAX  INTEGER (0..255)
    ACCESS  read-only
    STATUS  optional
    DESCRIPTION
        "This describes the state of the paper on the peripheral.
         When non-zero, the peripheral has a paper problem. When
         zero, the peripheral does not have a paper problem."
    ::={ gdStatusEntry 2 }

gdStatusInterventionState OBJECT-TYPE
    SYNTAX  INTEGER (0..255)
    ACCESS  read-only
    STATUS  optional
    DESCRIPTION
        "This describes the intervention state of the
         peripheral.  When non-zero, the peripheral requires
         human intervention to continue working.  When
         zero, it requires no assistance."
    ::={ gdStatusEntry 3 }

gdStatusNewMode OBJECT-TYPE
    SYNTAX  INTEGER (0..255)
    ACCESS  read-only
    STATUS  optional
    DESCRIPTION
        "This indicates to which read channel state the
         card should move.  When non-zero, the card should
         indicate that the read channel is idle.  When zero,
         the card should indicate that the read channel is
         operating."
    ::={ gdStatusEntry 4 }

gdStatusConnectionTerminationAck OBJECT-TYPE
    SYNTAX  INTEGER (0..255)
    ACCESS  read-only
    STATUS  optional
    DESCRIPTION
        "This indicates whether the peripheral is waiting for
         the Connection termination ACK.  When non-zero, it
         is waiting.  When zero, it is not waiting."
    ::={ gdStatusEntry 5 }

gdStatusPeripheralError OBJECT-TYPE
    SYNTAX  INTEGER (0..255)
    ACCESS  read-only
    STATUS  optional
    DESCRIPTION
        "This is the error code from the peripheral."
    ::={ gdStatusEntry 6 }

gdStatusIoChannelReset OBJECT-TYPE
    SYNTAX  INTEGER (0..255)
    ACCESS  read-only
    STATUS  optional
    DESCRIPTION
        "This indicates that the peripheral has requested the I/O
         card close the current connection.

         For some peripherals, such as the HP LaserJet IIISi printer
         or HP DesignJet plotter, this value is always a zero (0)."
    ::={ gdStatusEntry 7 }

gdStatusPaperOut OBJECT-TYPE
    SYNTAX  INTEGER {
                OFF(0),
                PAPER_OUT_OR_PAPER_MOUNT(1),
                MANUAL_PAPER_FEED_NEEDED(2)
            }
    ACCESS  read-only
    STATUS  optional
    DESCRIPTION
        "This indicates that the peripheral is out of paper.

         For some peripherals, such as the HP LaserJet IIISi printer
         or HP DesignJet plotter, this value is always a zero (0)."
    ::={ gdStatusEntry 8 }

gdStatusPaperJam OBJECT-TYPE
    SYNTAX  INTEGER {
                OFF(0),
                PAPER_JAM(1)
            }
    ACCESS  read-only
    STATUS  optional
    DESCRIPTION
        "This indicates that the peripheral has a paper jam.

         For some peripherals, such as the HP LaserJet IIISi printer
         or HP DesignJet plotter, this value is always a zero (0)."
    ::={ gdStatusEntry 9 }

gdStatusTonerLow OBJECT-TYPE
    SYNTAX  INTEGER {
                OFF(0),
                TONER_LOW(1),
                NO_TONER_CARTRIDGE(2)
            }
    ACCESS  read-only
    STATUS  optional
    DESCRIPTION
        "This indicates that the peripheral has a low toner condition.

         For some peripherals, such as the HP LaserJet IIISi printer
         or HP DesignJet plotter, this value is always a zero (0)."
    ::={ gdStatusEntry 10 }

gdStatusPagePunt OBJECT-TYPE
    SYNTAX  INTEGER (0..255)
    ACCESS  read-only
    STATUS  optional
    DESCRIPTION
        "This indicates that the peripheral did not receive data fast
         enough to keep up with the print engine when generating a page.

         For some peripherals, such as the HP LaserJet IIISi printer
         or HP DesignJet plotter, this value is always a zero (0)."
    ::={ gdStatusEntry 11 }

gdStatusMemoryOut OBJECT-TYPE
    SYNTAX  INTEGER (0..255)
    ACCESS  read-only
    STATUS  optional
    DESCRIPTION
        "This indicates that the peripheral did not have enough memory
         to render an image on a page.

         For some peripherals, such as the HP LaserJet IIISi printer
         or HP DesignJet plotter, this value is always a zero (0)."
    ::={ gdStatusEntry 12 }

gdStatusIoActive OBJECT-TYPE
    SYNTAX  INTEGER (0..255)
    ACCESS  read-only
    STATUS  optional
    DESCRIPTION
        "This indicates that the peripheral is processing data from
         this I/O interface card.

         For some peripherals, such as the HP LaserJet IIISi printer
         or HP DesignJet plotter, this value is always a zero (0)."
    ::={ gdStatusEntry 13 }

gdStatusBusy OBJECT-TYPE
    SYNTAX  INTEGER (0..255)
    ACCESS  read-only
    STATUS  optional
    DESCRIPTION
        "This indicates that the peripheral is busy processing
         print/plot data.

         For some peripherals, such as the HP LaserJet IIISi printer
         or HP DesignJet plotter, this value is always a zero (0)."
    ::={ gdStatusEntry 14 }

gdStatusWait OBJECT-TYPE
    SYNTAX  INTEGER (0..255)
    ACCESS  read-only
    STATUS  optional
    DESCRIPTION
        "This indicates that the peripheral is waiting for print/plot
         data to process.

         For some peripherals, such as the HP LaserJet IIISi printer
         or HP DesignJet plotter, this value is always a zero (0)."
    ::={ gdStatusEntry 15 }

gdStatusInitialize OBJECT-TYPE
    SYNTAX  INTEGER {
                OFF(0),
                INITIALIZING(1),
                WARM_UP(2)
            }
    ACCESS  read-only
    STATUS  optional
    DESCRIPTION
        "This indicates that the peripheral is initializing or
         warming up.

         For some peripherals, such as the HP LaserJet IIISi printer
         or HP DesignJet plotter, this value is always a zero (0)."
    ::={ gdStatusEntry 16 }

gdStatusDoorOpen OBJECT-TYPE
    SYNTAX  INTEGER (0..255)
    ACCESS  read-only
    STATUS  optional
    DESCRIPTION
        "This indicates that the peripheral cover or door is open.

         For some peripherals, such as the HP LaserJet IIISi printer
         or HP DesignJet plotter, this value is always a zero (0)."
    ::={ gdStatusEntry 17 }

gdStatusPrinting OBJECT-TYPE
    SYNTAX  INTEGER {
                OFF(0),
                ORDINARY_PAGE(1),
                TEST_FONTS_CONFIG_OR_START_PAGE(2)
            }
    ACCESS  read-only
    STATUS  optional
    DESCRIPTION
        "This indicates that the peripheral is printing or otherwise
         marking or moving paper.

         For some peripherals, such as the HP LaserJet IIISi printer
         or HP DesignJet plotter, this value is always a zero (0)."
    ::={ gdStatusEntry 18 }

gdStatusPaperOutput OBJECT-TYPE
    SYNTAX  INTEGER {
                OFF(0),
                OUTPUT_STORAGE_FULL(1)
            }
    ACCESS  read-only
    STATUS  optional
    DESCRIPTION
        "This indicates that the peripheral has a paper output problem
         such as the output storage bin being full.

         For some peripherals, such as the HP LaserJet IIISi printer
         or HP DesignJet plotter, this value is always a zero (0)."
    ::={ gdStatusEntry 19 }

gdStatusReserved OBJECT-TYPE
    SYNTAX  OCTET STRING (SIZE (0..13))
    ACCESS  read-only
    STATUS  optional
    DESCRIPTION
        "This is the reserved area that is not currently
         used, but will allow for growth within the gdStatusEntry table."
    ::={ gdStatusEntry 20 }


gdStatusDisplay OBJECT-TYPE
    SYNTAX  DisplayString (SIZE (0..255))
    ACCESS  read-only
    STATUS  optional
    DESCRIPTION
        "The string diplayed on the peripheral front panel.

         For some peripherals, such as the HP LaserJet IIISi printer
         or HP DesignJet plotter, this is always a zero length string."
    ::={ generalDeviceStatus 3 }

gdStatusJobName OBJECT-TYPE
    SYNTAX  DisplayString (SIZE (0..255))
    ACCESS  read-only
    STATUS  optional
    DESCRIPTION
        "The current job name set by the peripheral.

         For some peripherals, such as the HP LaserJet IIISi printer
         or HP DesignJet plotter, this is always a zero length string."
    ::={ generalDeviceStatus 4 }


-- the Ieee8023Mac group

ieee8023MacTable OBJECT-TYPE
    SYNTAX  SEQUENCE OF Ieee8023MacEntry
    ACCESS  not-accessible
    STATUS  mandatory
    DESCRIPTION
        "A list of ieee8023MacEntry entries."
    ::= { ieee8023Mac 1 }

ieee8023MacEntry OBJECT-TYPE
    SYNTAX  Ieee8023MacEntry
    ACCESS  not-accessible
    STATUS  mandatory
    DESCRIPTION
        "An entry containing the hp ieee8023 extentions."
    INDEX   { ieee8023MacIndex }
    ::= { ieee8023MacTable 1 }

Ieee8023MacEntry ::= SEQUENCE {
    ieee8023MacIndex
        INTEGER,
    ieee8023MacTransmitted
        Counter,
    ieee8023MacNotTransmitted
        Counter,
    ieee8023MacDeferred
        Counter,
    ieee8023MacCollisions
        Counter,
    ieee8023MacSingleCollisions
        Counter,
    ieee8023MacMultipleCollisions
        Counter,
    ieee8023MacExcessCollisions
        Counter,
    ieee8023MacLateCollisions
        Counter,
    ieee8023MacCarrierLostErrors
        Counter,
    ieee8023MacNoHeartBeatErrors
        Counter,
    ieee8023MacFramesReceived
        Counter,
    ieee8023MacUndeliverableFramesReceived
        Counter,
    ieee8023MacCrcErrors
        Counter,
    ieee8023MacAlignmentErrors
        Counter,
    ieee8023MacResourceErrors
        Counter,
    ieee8023MacControlFieldErrors
        Counter,
    ieee8023MacUnknownProtocolErrors
        Counter,
    ieee8023MacMulticastsAccepted
        Counter,
    ieee8023MacMulticastsAccepted
        Counter,
    ieee8023MacInfiniteDeferrals
        Counter,
    ieee8023MacUnderflowErrors
        Counter,
    ieee8023MacNoResources
        Counter,
    ieee8023MacLengthErrors
        Counter
}

ieee8023MacIndex OBJECT-TYPE
    SYNTAX  INTEGER
    ACCESS  read-only
    STATUS  mandatory
    DESCRIPTION
        "The index value which uniquely identifies the interface/port to
         which this entry is applicable.  The interface/port identified by
         a particular value of this index is the same interface/port as
         identified by the same value of ifIndex."
    ::= { ieee8023MacEntry 1 }

ieee8023MacTransmitted OBJECT-TYPE
    SYNTAX  Counter
    ACCESS  read-only
    STATUS  mandatory
    DESCRIPTION
        "The number of frames successfully transmitted."
    ::= { ieee8023MacEntry 2 }

ieee8023MacNotTransmitted OBJECT-TYPE
    SYNTAX  Counter
    ACCESS  read-only
    STATUS  mandatory
    DESCRIPTION
        "The number of frames not transmitted."
    ::= { ieee8023MacEntry 3 }

ieee8023MacDeferred OBJECT-TYPE
    SYNTAX  Counter
    ACCESS  read-only
    STATUS  mandatory
    DESCRIPTION
        "Number of frames which were successfully transmitted after a
         deferral.  If any collisions occurred before transmission,
         xmtDeferredTransmission isn't incremented."
    ::= { ieee8023MacEntry 4 }

ieee8023MacCollisions OBJECT-TYPE
    SYNTAX  Counter
    ACCESS  read-only
    STATUS  mandatory
    DESCRIPTION
        "Total number of transmit attempts that were retransmitted due to
         collisions, and are subsequently transmitted successfully."
    ::= { ieee8023MacEntry 5 }

ieee8023MacSingleCollisions OBJECT-TYPE
    SYNTAX  Counter
    ACCESS  read-only
    STATUS  mandatory
    DESCRIPTION
        "Number of transmit attempts that are involved in a single
         collision, and are subsequently transmitted successfully."
    ::= { ieee8023MacEntry 6 }

ieee8023MacMultipleCollisions OBJECT-TYPE
    SYNTAX  Counter
    ACCESS  read-only
    STATUS  mandatory
    DESCRIPTION
        "Number of transmit attempts that are involved in between one and
         fifteen collision attempts, and are subsequently transmitted
         successfully."
    ::= { ieee8023MacEntry 7 }

ieee8023MacExcessCollisions OBJECT-TYPE
    SYNTAX  Counter
    ACCESS  read-only
    STATUS  mandatory
    DESCRIPTION
        "The number of transmits that occur after more than 15 collisions,
         and are subsequently transmitted successfully."
    ::= { ieee8023MacEntry 8 }

ieee8023MacLateCollisions OBJECT-TYPE
    SYNTAX  Counter
    ACCESS  read-only
    STATUS  mandatory
    DESCRIPTION
        "The number of collisions that occured after one end-to-end frame
         propagation delay."
    ::= { ieee8023MacEntry 9 }

ieee8023MacCarrierLostErrors OBJECT-TYPE
    SYNTAX  Counter
    ACCESS  read-only
    STATUS  mandatory
    DESCRIPTION
        "Number of times that carrier sense was lost when attempting to
         transmit."
    ::= { ieee8023MacEntry 10 }

ieee8023MacNoHeartBeatErrors OBJECT-TYPE
    SYNTAX  Counter
    ACCESS  read-only
    STATUS  mandatory
    DESCRIPTION
        "The number of times the MAU failed to assert SQE after
         transmitting a packet."
    ::= { ieee8023MacEntry 11 }

ieee8023MacFramesReceived OBJECT-TYPE
    SYNTAX  Counter
    ACCESS  read-only
    STATUS  mandatory
    DESCRIPTION
        "The number of frames successfully received."
    ::= { ieee8023MacEntry 12 }

ieee8023MacUndeliverableFramesReceived OBJECT-TYPE
    SYNTAX  Counter
    ACCESS  read-only
    STATUS  mandatory
    DESCRIPTION
        "The number of frames received that could not be delivered because
         the software buffer was overrun when frames were sent faster than
         they could be received."
    ::= { ieee8023MacEntry 13 }

ieee8023MacCrcErrors OBJECT-TYPE
    SYNTAX  Counter
    ACCESS  read-only
    STATUS  mandatory
    DESCRIPTION
        "The number of Cyclical Redundancy Check (CRC) errors detected."
    ::= { ieee8023MacEntry 14 }

    ieee8023MacAlignmentErrors OBJECT-TYPE
    SYNTAX  Counter
    ACCESS  read-only
    STATUS  mandatory
    DESCRIPTION
        "The number of frames received that were both misaligned and had
         bad CRC."
    ::= { ieee8023MacEntry 15 }

ieee8023MacResourceErrors OBJECT-TYPE
    SYNTAX  Counter
    ACCESS  read-only
    STATUS  mandatory
    DESCRIPTION
        "The number of frames received that were lost due to lack of
         resources."
    ::= { ieee8023MacEntry 16 }

ieee8023MacControlFieldErrors OBJECT-TYPE
    SYNTAX  Counter
    ACCESS  read-only
    STATUS  mandatory
    DESCRIPTION
        "The number of frames received with errors in the control field."
    ::= { ieee8023MacEntry 17 }

ieee8023MacUnknownProtocolErrors OBJECT-TYPE
    SYNTAX  Counter
    ACCESS  read-only
    STATUS  mandatory
    DESCRIPTION
        "The number frames dropped because the type field or sap field
         referenced an invalid protocol."
    ::= { ieee8023MacEntry 18 }

ieee8023MacMulticastsAccepted OBJECT-TYPE
    SYNTAX  Counter
    ACCESS  read-only
    STATUS  mandatory
    DESCRIPTION
        "Number of accepted muliticast addresses."
    ::= { ieee8023MacEntry 19 }

ieee8023MacInfiniteDeferrals OBJECT-TYPE
    SYNTAX  Counter
    ACCESS  read-only
    STATUS  mandatory
    DESCRIPTION
        "The number of frames not transmitted successfully
         due to excessive number of deferrals."
    ::= { ieee8023MacEntry 20 }

ieee8023MacUnderflowErrors OBJECT-TYPE
    SYNTAX  Counter
    ACCESS  read-only
    STATUS  mandatory
    DESCRIPTION
        "The number of frames not transmitted successfully
         because an underflow occurred on the transmit."
    ::= { ieee8023MacEntry 21 }

ieee8023MacNoResources OBJECT-TYPE
    SYNTAX  Counter
    ACCESS  read-only
    STATUS  mandatory
    DESCRIPTION
        "The number of frames not transmitted successfully
         because the MAC lacked resources to handle the frame."
    ::= { ieee8023MacEntry 22 }

ieee8023MacLengthErrors OBJECT-TYPE
    SYNTAX  Counter
    ACCESS  read-only
    STATUS  mandatory
    DESCRIPTION
        "The number of frames received that have length errors."
    ::= { ieee8023MacEntry 23 }


--  The 802.3 Multicast Address Table

ieee8023MacMcaTable OBJECT-TYPE
    SYNTAX  SEQUENCE OF Ieee8023MacMcaTableEntry
    ACCESS  not-accessible
    STATUS  optional
    DESCRIPTION
        "The 802.3 multicast address table."
    ::= { ieee8023Mac 2 }

ieee8023MacMcaTableEntry OBJECT-TYPE
    SYNTAX  Ieee8023MacMcaTableEntry
    ACCESS  not-accessible
    STATUS  optional
    DESCRIPTION
        "Entries in the ieee8023MacMcaTable."
    ::= { ieee8023MacMcaTable 1 }

Ieee8023MacMcaTableEntry ::=
    SEQUENCE {
        ieee8023MacMcaIndex
            INTEGER,
        ieee8023MacMcaAddress
            OCTET STRING
    }

ieee8023MacMcaIndex OBJECT-TYPE
    SYNTAX  INTEGER
    ACCESS  read-only
    STATUS  optional
    DESCRIPTION
        "The index corresponding to a particular instance
         in the ieee8023MacMcaTable."
    ::= { ieee8023MacMcaTableEntry 1 }

ieee8023MacMcaAddress OBJECT-TYPE
    SYNTAX  OCTET STRING
    ACCESS  read-only
    STATUS  optional
    DESCRIPTION
        "The multicast address of a particular instance in
         the ieee8023McaTable."
    ::= { ieee8023MacMcaTableEntry 2 }


--  Other 802.3 Objects

ieee8023MacState OBJECT-TYPE
    SYNTAX  INTEGER {
                OFFLINE(1),
                INITIALIZING(2),
                ONLINE(4),
                ERROR(5),
                IO_NOT_READY(6)
            }
    ACCESS  read-only
    STATUS  optional
    DESCRIPTION
        "The internal state of this instance."
    ::= { ieee8023Mac 3 }

ieee8023MacConfigurationStatus OBJECT-TYPE
    SYNTAX  INTEGER {
                INTERNAL_MAU_SELECTED1(1),
                INTERNAL_MAU_SELECTED5(5),
                INTERNAL_MAU_SELECTED13(13),
                EXTERNAL_MAU_SELECTED(14)
            }
    ACCESS  read-only
    STATUS  optional
    DESCRIPTION
        "This is the four bits of hardware power sense and
         jumper sense registers:

            15  14  13  12  11
            +---+---+---+---+----------+
            |apa|mpa|ext|int|  unused  |
            +---+---+---+---+----------+

            unused    Reserved for future status.
            apa       12v power detected at the AUI connector.
            mpa       12v power detected at the Peripheral
            interface.
            ext       External AUI connector selected.
            int       Internal tranceiver selected."
    ::= { ieee8023Mac 4 }

ieee8023MacNumberActiveMCAs OBJECT-TYPE
    SYNTAX  INTEGER
    ACCESS  read-only
    STATUS  optional
    DESCRIPTION
        "The number of entries in the multicast address table."
    ::= { ieee8023Mac 5 }


-- The HP Network Peripheral Card (npCard) Group
-- The System subgroup of npCard

npSysState OBJECT-TYPE
    SYNTAX  INTEGER {
                Offline(1),
                Initializing(2),
                Online(4),
                Error(5),
                IO_NOT_READY(6)
            }
    ACCESS  read-only
    STATUS  optional
    DESCRIPTION
        "The state of the LAN card to network peripheral
         interface driver."
    ::={ npSys 1 }

npSysStatusMessage OBJECT-TYPE
    SYNTAX  DisplayString (SIZE (0..255))
    ACCESS  read-only
    STATUS  optional
    DESCRIPTION
        "A status string reflecting the current state of the card
         and peripheral."
    ::={ npSys 2 }

npSysPeripheralFatalError OBJECT-TYPE
    SYNTAX  INTEGER (0..255)
    ACCESS  read-only
    STATUS  optional
    DESCRIPTION
        "The most recent peripheral fatal error that is
         being displayed on the peripheral's display panel.
         The error typically appears as a '80 Service
         (00xx)' error.  Refer to peripheral documentation
         to determine what the error means."
    ::={ npSys 3 }

npSysCardFatalError OBJECT-TYPE
    SYNTAX  INTEGER (0..255)
    ACCESS  read-only
    STATUS  optional
    DESCRIPTION
        "The most recent LAN Card error that is being
         displayed on the peripheral's display panel.  The
         error typically appears as a '80 Service (01xx)'
         error.  Refer to peripheral documentation to
         determine what the error means."
    ::={ npSys 4 }

npSysMaximumWriteBuffers OBJECT-TYPE
    SYNTAX  INTEGER
    ACCESS  read-only
    STATUS  optional
    DESCRIPTION
        "The maximum number of write buffers configured for
         the LAN card (this translates to the write window
         size of the connection)."
    ::={ npSys 5 }

npSysMaximumReadBuffers OBJECT-TYPE
    SYNTAX  INTEGER
    ACCESS  read-only
    STATUS  optional
    DESCRIPTION
        "The maximum number of read buffers configured for
         the LAN card (this translates to the read window
         size of the connection)."
    ::={ npSys 6 }

npSysTotalBytesRecvs OBJECT-TYPE
    SYNTAX  Counter
    ACCESS  read-only
    STATUS  optional
    DESCRIPTION
        "The total number of bytes received since reset."
    ::={ npSys 7 }

npSysTotalBytesSents OBJECT-TYPE
    SYNTAX  Counter
    ACCESS  read-only
    STATUS  optional
    DESCRIPTION
        "The total number of bytes sent since reset."
    ::={ npSys 8 }

npSysCurrReadReq OBJECT-TYPE
    SYNTAX  Gauge
    ACCESS  read-only
    STATUS  optional
    DESCRIPTION
        "The current number of read data buffers owned by
         the LAN card."
    ::={ npSys 9 }


-- The HP Modular Input/Output (MIO) subgroup of npCard
-- The Card Status Entry

npNpiCardStatusEntry OBJECT-TYPE
    SYNTAX  npNpiStatusEntry
    ACCESS  read-only
    STATUS  optional
    DESCRIPTION
        "These are the set of status bytes that the
         peripheral passes to the network card.  The
         peripheral and LAN card exchange these status
         bytes whenever an event causes the status to
         change."
    ::={ npNpi 1 }

npNpiCardStatusEntry ::=
    SEQUENCE {
        npNpiCseDataState
            INTEGER,
        npNpiCseErrorCode
            INTEGER,
        npNpiCseLinkEvent
            INTEGER,
        npNpiCseReadMode
            INTEGER,
        npNpiCseWriteMode
            INTEGER,
        npNpiCseWarningCode
            INTEGER,
        npNpiCseConnectionState
            INTEGER
}

npNpiCseDataState OBJECT-TYPE
    SYNTAX  INTEGER (0..255)
    ACCESS  read-only
    STATUS  optional
    DESCRIPTION
        "The data state of the LAN card."
    ::={ npNpiCardStatusEntry 1 }

npNpiCseErrorCode OBJECT-TYPE
    SYNTAX  INTEGER (0..255)
    ACCESS  read-only
    STATUS  optional
    DESCRIPTION
        "The LAN card's error code."
    ::={ npNpiCardStatusEntry 2 }

npNpiCseLinkEvent OBJECT-TYPE
    SYNTAX  INTEGER (0..255)
    ACCESS  read-only
    STATUS  optional
    DESCRIPTION
        "The LAN link event (reset or initialized or
         triggered)."
    ::={ npNpiCardStatusEntry 3 }

npNpiCseReadMode OBJECT-TYPE
    SYNTAX  INTEGER (0..255)
    ACCESS  read-only
    STATUS  optional
    DESCRIPTION
        "The state of the LAN card's read channel (operate
         or idle)."
    ::={ npNpiCardStatusEntry 4 }

npNpiCseWriteMode OBJECT-TYPE
    SYNTAX  INTEGER (0..255)
    ACCESS  read-only
    STATUS  optional
    DESCRIPTION
        "The state of the LAN card's write channel (operate
         or idle)."
    ::={ npNpiCardStatusEntry 5 }

npNpiCseWarningCode OBJECT-TYPE
    SYNTAX  INTEGER (0..255)
    ACCESS  read-only
    STATUS  optional
    DESCRIPTION
        "This indicates that the LAN card has enCountered
         an error condition which isn't serious enough to
         shut the peripheral down, but should be checked
         out."
    ::={ npNpiCardStatusEntry 6 }

npNpiCseConnectionState OBJECT-TYPE
    SYNTAX  INTEGER (0..255)
    ACCESS  read-only
    STATUS  optional
    DESCRIPTION
        "Indicates whether or not the peripheral is
         currently connected to a server."
    ::={ npNpiCardStatusEntry 7 }



--  The Peripheral Attribute Entry

npNpiPeripheralAttributeCount OBJECT-TYPE
    SYNTAX  INTEGER (0..32)
    ACCESS  read-only
    STATUS  optional
    DESCRIPTION
        "The number of valid bytes of peripheral attributes
         received from the peripheral."
    ::={ npNpi 2 }

npNpiPeripheralAttributeEntry OBJECT-TYPE
    SYNTAX  npNpiPeripheralAttributeEntry
    ACCESS  read-only
    STATUS  optional
    DESCRIPTION
        "The set of bytes that describe the peripheral's
         attributes as received from the peripheral during
         the setup of the peripheral to LAN card
         communications."
    ::={ npNpi 3 }

npNpiPeripheralAttributeEntry ::=
    SEQUENCE {
        npNpiPaeLinkDirection
            INTEGER,
        npNpiPaeClass
            INTEGER,
        npNpiPaeIdentification
            INTEGER,
        npNpiPaeRevision
            INTEGER,
        npNpiPaeAppleTalk
            INTEGER,
        npNpiPaeMessage
            INTEGER,
        npNpiPaeVideoFlag
            INTEGER,
        npNpiPaeReserved
            OCTET STRING
}

npNpiPaeLinkDirection OBJECT-TYPE
    SYNTAX  INTEGER {
                NO_PERIPH_DATA_XFER(0),
                XFER_PERIPH_TO_HOST(1),
                XFER_HOST_TO_PERIPH(2),
                BI_DIRECT_PERIPH_DATA_XFER(3)
            }
    ACCESS  read-only
    STATUS  optional
    DESCRIPTION
        "The directions that the peripheral is able to
         transfer data (read and write channels, read
         channel only, or write channel only)."
    ::={ npNpiPeripheralAttributeEntry 1 }

npNpiPaeClass OBJECT-TYPE
    SYNTAX  INTEGER {
                UNDEFINED_CLASS(0),
                PRINTER(1),
                PLOTTER(2),
                INSTRUMENT(3)
            }
    ACCESS  read-only
    STATUS  optional
    DESCRIPTION
        "The class assigned to the peripheral onto which
         this card is plugged."
    ::={ npNpiPeripheralAttributeEntry 2 }

npNpiPaeIdentification OBJECT-TYPE
    SYNTAX  INTEGER {
                UNDEFINED_PERIPH(0),
                LASERJET_IIISI(1)
            }
    ACCESS  read-only
    STATUS  optional
    DESCRIPTION
        "The Identification number of the peripheral."
    ::={ npNpiPeripheralAttributeEntry 3 }

npNpiPaeRevision OBJECT-TYPE
    SYNTAX  INTEGER (0..255)
    ACCESS  read-only
    STATUS  optional
    DESCRIPTION
        "The revision number of the peripheral."
    ::={ npNpiPeripheralAttributeEntry 4 }

npNpiPaeAppleTalk OBJECT-TYPE
    SYNTAX  INTEGER {
                NO_APPLETALK_SUPPORT(0),
                APPLETALK_SUPPORT(1)
            }
    ACCESS  read-only
    STATUS  optional
    DESCRIPTION
        "Indicates the peripheral supports functionality
         that the apple talk protocol network provides."
    ::={ npNpiPeripheralAttributeEntry 5 }

npNpiPaeMessage OBJECT-TYPE
    SYNTAX  INTEGER {
                NO_MSGMODE_SUPPORT(0),
                MSGMODE_SUPPORT(1)
            }
    ACCESS  read-only
    STATUS  optional
    DESCRIPTION
        "Reserved for future use."
    ::={ npNpiPeripheralAttributeEntry 6 }

npNpiPaeVideoFlag OBJECT-TYPE
    SYNTAX  INTEGER {
                NO_VIDEOXFER_SUPPORT(0),
                VIDEOXFER_SUPPORT(1)
            }
    ACCESS  read-only
    STATUS  optional
    DESCRIPTION
        "Indicates the peripheral supports the 3.63 Mhz /
         7.26 Mhz video data transfer hardware."
    ::={ npNpiPeripheralAttributeEntry 7 }

npNpiPaeReserved OBJECT-TYPE
    SYNTAX  OCTET STRING (SIZE (0..8))
    ACCESS  read-only
    STATUS  optional
    DESCRIPTION
        "Padding where future revisions of the peripheral may
         put things.  Allows Net management to stay the same
         in the future."
    ::={ npNpiPeripheralAttributeEntry 8 }



--  The Card Attribute Entry

npNpiCardAttributeEntry OBJECT-TYPE
    SYNTAX  npNpiCardAttributeEntry 
    ACCESS  read-only
    STATUS  optional
    DESCRIPTION
        "The set of bytes describing the card's attributes
         as stored in the ROM of this particular LAN card."
    ::={ npNpi 4 }

npNpiCardAttributeEntry ::=
    SEQUENCE {
        npNpiCaeLinkDirection
            INTEGER,
        npNpiCaeClass
            INTEGER,
        npNpiCaeIdentification
            INTEGER,
        npNpiCaeRevision
            INTEGER,
        npNpiCaeAppleTalk
            INTEGER,
        npNpiCaeMessage
            INTEGER
}

npNpiCaeLinkDirection OBJECT-TYPE
    SYNTAX  INTEGER {
                NO_LINK_DATA_XFER(0),
                XFER_LINK_TO_HOST(1),
                XFER_HOST_TO_LINK(2),
                BI_DIRECT_LINK_DATA_XFER(3)
            }
    ACCESS  read-only
    STATUS  optional
    DESCRIPTION
        "The directions that this particular network
         peripheral card is able to transfer data (read and
         write, read only or write only)."
    ::={ npNpiCardAttributeEntry 1 }

npNpiCaeClass OBJECT-TYPE
    SYNTAX  INTEGER {
                UNDEFINED_CLASS(0),
                RS_232(1),
                CENTRONICS(2),
                CSMD_CD_NETWORK(3),
                TOKEN_RING_NETWORK(4),
                SCSI(5),
                HPIB(6),
                LOCALTALK(7)
            }
    ACCESS  read-only
    STATUS  optional
    DESCRIPTION
        "The class of this network peripheral card."
    ::={ npNpiCardAttributeEntry 2 }

npNpiCaeIdentification OBJECT-TYPE
    SYNTAX  INTEGER (0..65535)
    ACCESS  read-only
    STATUS  optional
    DESCRIPTION
        "The identification number assigned this network
         peripheral card."
    ::={ npNpiCardAttributeEntry 3 }

npNpiCaeRevision OBJECT-TYPE
    SYNTAX  INTEGER (0..255)
    ACCESS  read-only
    STATUS  optional
    DESCRIPTION
        "The revision number of the network peripheral
         connection card code on this card."
    ::={ npNpiCardAttributeEntry 4 }

npNpiCaeAppleTalk OBJECT-TYPE
    SYNTAX  INTEGER {
                NO_APPLETALK_SUPPORT(0),
                APPLETALK_SUPPORT(1)
            }
    ACCESS  read-only
    STATUS  optional
    DESCRIPTION
        "Indicates that the card supports the apple talk
         protocol network."
    ::={ npNpiCardAttributeEntry 5 }

npNpiCaeMessage OBJECT-TYPE
    SYNTAX  INTEGER {
                NO_MSGMODE_SUPPORT(0),
                MSGMODE_SUPPORT(1)
            }
    ACCESS  read-only
    STATUS  optional
    DESCRIPTION
        "Indicates that the card supports the messaging mode protocol."
    ::={ npNpiCardAttributeEntry 6 }



--  The Error Log Table subgroup of npCard

npEltErrorLogTable OBJECT-TYPE
    SYNTAX  npEltErrorLogTable
    ACCESS  read-only
    STATUS  optional
    DESCRIPTION
        "The LAN card's error log."
    ::={ npElt 1 }

npEltEntry OBJECT-TYPE
    SYNTAX  npEltErrorLogTable
    ACCESS  read-only
    STATUS  optional
    DESCRIPTION
        "The LAN card's error log table entries."
    ::={ npEltErrorLogTable 1 }

npEltErrorLogTable ::=
    SEQUENCE {
        npEltErrIndex
            INTEGER,
        npEltErrErrorId
            INTEGER,
        npEltErrErrorParam
            INTEGER,
        npEltErrTimeStamp
            TimeTicks
    }

npEltErrIndex OBJECT-TYPE
    SYNTAX  INTEGER (0..255)
    ACCESS  read-only
    STATUS  optional
    DESCRIPTION
        "The index that uniquely identifies an error log
         entry."
    ::={ npEltEntry 1 }

npEltErrErrorId OBJECT-TYPE
    SYNTAX  INTEGER (0..65535)
    ACCESS  read-only
    STATUS  optional
    DESCRIPTION
        "Identification for this error."
    ::={ npEltEntry 2 }

npEltErrErrorParam OBJECT-TYPE
    SYNTAX  INTEGER (0..4294967295)
    ACCESS  read-only
    STATUS  optional
    DESCRIPTION
        "Error Parameter value."
    ::={ npEltEntry 3 }

npEltErrTimeStamp OBJECT-TYPE
    SYNTAX  TimeTicks
    ACCESS  read-only
    STATUS  optional
    DESCRIPTION
        "Time in timer ticks when error log entry was made."
    ::={ npEltEntry 4 }


--- The Card Connection Statistics subgroup of npCard

npConnsAccepts OBJECT-TYPE
    SYNTAX  Counter
    ACCESS  read-only
    STATUS  optional
    DESCRIPTION
        "The number of connections accepted since reset."
    ::={ npConns 1 }

npConnsRefused OBJECT-TYPE
    SYNTAX  Counter
    ACCESS  read-only
    STATUS  optional
    DESCRIPTION
        "The number of connections refused since reset.  Connections
         are refused for the following reasons: a connection is already
         active, the peripheral is offline, the network peripheral
         interface is not ready for connections after a power-up or
         reset, or there isn't enough buffer space on the card to
         establish a connection."
    ::={ npConns 2 }

npConnsDenys OBJECT-TYPE
    SYNTAX  Counter
    ACCESS  read-only
    STATUS  optional
    DESCRIPTION
        "The number of connections that the card denied due to failure
         to match the access list."
    ::={ npConns 3 }

npConnsDenysIP OBJECT-TYPE
    SYNTAX  IpAddress
    ACCESS  read-only
    STATUS  optional
    DESCRIPTION
        "The IP address of the last node to be denied a connection
         due to failure to match the access list."
    ::={ npConns 4 }

npConnsAborts OBJECT-TYPE
    SYNTAX  Counter
    ACCESS  read-only
    STATUS  optional
    DESCRIPTION
        "The number of connections aborted due to a network problem."
    ::={ npConns 5 }

npConnsAbortReason OBJECT-TYPE
    SYNTAX  DisplayString (SIZE (0..255))
    ACCESS  read-only
    STATUS  optional
    DESCRIPTION
        "The textual description of why the last abort on the
         card occurred."
    ::={ npConns 6 }

npConnsAbortIP OBJECT-TYPE
    SYNTAX  IpAddress
    ACCESS  read-only
    STATUS  optional
    DESCRIPTION
        "The IP address of the last node to establish a connection
         before the card aborted."
    ::={ npConns 7 }

npConnsAbortPort OBJECT-TYPE
    SYNTAX  INTEGER (0..65535)
    ACCESS  read-only
    STATUS  optional
    DESCRIPTION
        "The port of the last node to establish a connection
         before the card aborted."
    ::={ npConns 8 }

npConnsAbortTime OBJECT-TYPE
    SYNTAX  TimeTicks
    ACCESS  read-only
    STATUS  optional
    DESCRIPTION
        "The time (in hundredths of a second) since the last
         time the card was aborted."
    ::={ npConns 9 }

npConnsState OBJECT-TYPE
    SYNTAX  INTEGER {
                up(1),
                down(2)
            }
    ACCESS  read-only
    STATUS  optional
    DESCRIPTION
        "State of current connection to card."
    ::={ npConns 10 }

npConnsIP OBJECT-TYPE
    SYNTAX  IpAddress
    ACCESS  read-only
    STATUS  optional
    DESCRIPTION
        "Remote IP address of the node currently connected to the card.
         Zero if no connection is active."
    ::={ npConns 11 }

npConnsPort OBJECT-TYPE
    SYNTAX  INTEGER (0..65535)
    ACCESS  read-only
    STATUS  optional
    DESCRIPTION
        "Remote port number of the node currently connected to the card.
         Zero if no connection is active."
    ::={ npConns 12 }

npConnsPeriphClose OBJECT-TYPE
    SYNTAX  INTEGER
    ACCESS  read-only
    STATUS  optional
    DESCRIPTION
        "The number of connections closed in response to a peripheral
         request I/O channel reset request."
    ::={ npConns 13 }

npConnsIdleTimeouts OBJECT-TYPE
    SYNTAX  INTEGER
    ACCESS  read-only
    STATUS  optional
    DESCRIPTION
        "The number of connections closed due to an idle timeout."
    ::={ npConns 14 }

npConnsNmClose OBJECT-TYPE
    SYNTAX  INTEGER
    ACCESS  read-only
    STATUS  optional
    DESCRIPTION
        "The number of connections closed by SetRequests to the MIB
         variable, npCtlCloseConnection."
    ::={ npConns 15 }

npConnsBytesRecvd OBJECT-TYPE
    SYNTAX  Counter
    ACCESS  read-only
    STATUS  optional
    DESCRIPTION
        "The number of bytes received by this connection."
    ::={ npConns 16 }

npConnsBytesSent OBJECT-TYPE
    SYNTAX  Counter
    ACCESS  read-only
    STATUS  optional
    DESCRIPTION
        "The number of bytes transmitted by this connection."
    ::={ npConns 17 }


--- The Card Configuration subgroup of npCard

npCfgSource OBJECT-TYPE
    SYNTAX  INTEGER {
                BOOTP(0),
                FRONTPANEL(1)
            }
    ACCESS  read-only
    STATUS  optional
    DESCRIPTION
        "This indicates whether the card obtained its configuration
         from the system that sent the BOOTP reply or from the
         front panel."
    ::={ npCfg 1 }

npCfgYiaddr OBJECT-TYPE
    SYNTAX  IpAddress
    ACCESS  read-only
    STATUS  optional
    DESCRIPTION
        "The IP address assigned to the card from the BOOTP reply
         yiaddr field."
    ::={ npCfg 2 }

npCfgSiaddr OBJECT-TYPE
    SYNTAX  IpAddress
    ACCESS  read-only
    STATUS  optional
    DESCRIPTION
        "The IP address of the TFTP server from the BOOTP reply
         siaddr field."
    ::={ npCfg 3 }

npCfgGiaddr OBJECT-TYPE
    SYNTAX  IpAddress
    ACCESS  read-only
    STATUS  optional
    DESCRIPTION
        "The IP address of the TFTP gateway from the BOOTP reply
         giaddr field."
    ::={ npCfg 4 }

npCfgLogServer OBJECT-TYPE
    SYNTAX  IpAddress
    ACCESS  read-only
    STATUS  optional
    DESCRIPTION
        "The IP address of the Log Server from the BOOTP reply
         Tag: 7 field."
    ::={ npCfg 5 }

npCfgSyslogFacility OBJECT-TYPE
    SYNTAX  INTEGER
    ACCESS  read-only
    STATUS  optional
    DESCRIPTION
        "This specifies the facility identifier used in syslog messages
         generated by the card."
    ::={ npCfg 6 }

npCfgAccessState OBJECT-TYPE
    SYNTAX  INTEGER {
                allowed(1),
                not-allowed(2)
            }
    ACCESS  read-only
    STATUS  optional
    DESCRIPTION
        "An indication of whether or not the requesting host
         is allowed to connect to the card as dictated by the
         access list."
    ::={ npCfg 7 }

npCfgAccessListNum OBJECT-TYPE
    SYNTAX  INTEGER
    ACCESS  read-only
    STATUS  optional
    DESCRIPTION
        "The number of access list entries."
    ::={ npCfg 8 }

npCfgAccessListTable OBJECT-TYPE
    SYNTAX  SEQUENCE OF AccessListEntry
    ACCESS  read-only
    STATUS  optional
    DESCRIPTION
        "List of access addresses and masks."
    ::={ npCfg 9 }

accessListEntry OBJECT-TYPE
    SYNTAX  AccessListEntry
    ACCESS  read-only
    STATUS  optional
    DESCRIPTION
        "Each entry contains an access address and mask."
    INDEX    { npCfgAccessListIndex }
    ::={ npCfgAccessListTable 1 }

AccessListEntry ::=
    SEQUENCE {
        npCfgAccessListIndex
            INTEGER,
        npCfgAccessListAddress
            IpAddress,
        npCfgAccessListAddrMask
            IpAddress
    }

npCfgAccessListIndex OBJECT-TYPE
    SYNTAX  INTEGER (0..9)
    ACCESS  read-only
    STATUS  optional
    DESCRIPTION
        "Index to the configuration access list table."
    ::={ accessListEntry 1 }

npCfgAccessListAddress OBJECT-TYPE
    SYNTAX  IpAddress
    ACCESS  read-only
    STATUS  optional
    DESCRIPTION
        "Address to compare with after applying the wildcard to
         the requestor's address."
    ::={ accessListEntry 2 }

npCfgAccessListAddrMask OBJECT-TYPE
    SYNTAX  IpAddress
    ACCESS  read-only
    STATUS  optional
    DESCRIPTION
        "Address mask used to help determine whether or not a given
         IP address is allowed access to the card.  An IP address is
         allowed access if (Addr & AddrMask) == (IP & AddrMask)."
    ::={ accessListEntry 3 }

npCfgIdleTimeout OBJECT-TYPE
    SYNTAX  INTEGER
    ACCESS  read-only
    STATUS  optional
    DESCRIPTION
        "The idle timeout is the length in seconds after which an
         idle connection is terminated.  A value of zero disables
         the timeout."
    ::={ npCfg 10 }

npCfgLocalSubnets OBJECT-TYPE
    SYNTAX  INTEGER {
                none(0),
                exist(1)
            }
    ACCESS  read-only
    STATUS  optional
    DESCRIPTION
        "An indication of whether or not the card recognizes
         any local subnets."
    ::={ npCfg 11 }


-- The TCP subgroup of npCard

npTcpInSegInOrder OBJECT-TYPE
    SYNTAX  Counter
    ACCESS  read-only
    STATUS  optional
    DESCRIPTION
        "The number of TCP segments received in order."
    ::={ npTcp 1 }

npTcpInSegOutOfOrder OBJECT-TYPE
    SYNTAX  Counter
    ACCESS  read-only
    STATUS  optional
    DESCRIPTION
        "The number of TCP segments received out of order."
    ::={ npTcp 2 }

npTcpInSegZeroProbe OBJECT-TYPE
    SYNTAX  Counter
    ACCESS  read-only
    STATUS  optional
    DESCRIPTION
        "The number of TCP zero window probes received."
    ::={ npTcp 3 }

npTcpInDiscards OBJECT-TYPE
    SYNTAX  Counter
    ACCESS  read-only
    STATUS  optional
    DESCRIPTION
        "The number of TCP segments received that were
         discarded."
    ::={ npTcp 4 }


-- The Card Control subgroup of npCard

npCtlReconfigIP OBJECT-TYPE
    SYNTAX  IpAddress
    ACCESS  read-only
    STATUS  optional
    DESCRIPTION
        "The IP address of the last node to request a reconfig
         of the card.  This value is preserved across a reconfig."
    ::={ npCtl 1 }

npCtlReconfigPort OBJECT-TYPE
    SYNTAX  INTEGER (0..65535)
    ACCESS  read-only
    STATUS  optional
    DESCRIPTION
        "The port of the last node to request a reconfig of the
         card.  This value is preserved across a reconfig."
    ::={ npCtl 2 }

npCtlReconfigTime OBJECT-TYPE
    SYNTAX  TimeTicks
    ACCESS  read-only
    STATUS  optional
    DESCRIPTION
        "The time (in hundredths of a second) since the last
         time the card was reconfigured."
    ::={ npCtl 3 }

npCtlCloseIP OBJECT-TYPE
    SYNTAX  IpAddress
    ACCESS  read-only
    STATUS  optional
    DESCRIPTION
        "The IP address of the last node to request a close of
         the peripheral data connection on the card.  This
         value is cleared on a reconfig."
    ::={ npCtl 4 }

npCtlClosePort OBJECT-TYPE
    SYNTAX  INTEGER (0..65535)
    ACCESS  read-only
    STATUS  optional
    DESCRIPTION
        "The port of the last node to request a close of the
         peripheral data connection on the card.  This
         value is cleared on a reconfig."
    ::={ npCtl 5 }

npCtlImageDump OBJECT-TYPE
    SYNTAX  INTEGER {
                OFF(0),
                DUMP(1)
            }
    ACCESS  read-write
    STATUS  optional
    DESCRIPTION
        "Writing a one (1) to this variable causes the card to dump
         its RAM image into a file using TFTP.  The file is dumped
         onto the BOOTP server machine whose IP address is in the MIB
         variable, npCfgSiaddr { npCfg 3 }.  The file name is:
         npi.<IPaddr> in the tftp directory, where <IPaddr> is the
         IP address of the card.  The file must be writable by TFTP."
    ::= { npCtl 6 }

npCtlCloseConnection OBJECT-TYPE
    SYNTAX  INTEGER {
                OFF(0),
                CLOSE(1)
            }
    ACCESS  read-write
    STATUS  optional
    DESCRIPTION
        "Writing a one (1) to this variable causes the card to close
         the current peripheral data connection"
    ::= { npCtl 7 }

npCtlReconfig OBJECT-TYPE
    SYNTAX  INTEGER {
                OFF(0),
                REBOOT(1)
            }
    ACCESS  read-write
    STATUS  optional
    DESCRIPTION
        "Writing a one (1) to this variable causes the card to
         reconfigure itself by doing the BOOTP/TFTP configuration
         activity."
    ::= { npCtl 8 }


--- The Trap Group

trapDestinationNum OBJECT-TYPE
    SYNTAX  INTEGER
    ACCESS  read-only
    STATUS  optional
    DESCRIPTION
        "The number of trap destinations."
    ::={ trap 1 }

-- The Trap Destination Table

trapDestinationTable OBJECT-TYPE
    SYNTAX  SEQUENCE OF TrapDestinationEntry
    ACCESS  read-only
    STATUS  mandatory
    DESCRIPTION
        "List of addresses to which the agent sends traps."
    ::= { trap 2 }

trapDestinationEntry OBJECT-TYPE
    SYNTAX  TrapDestinationEntry
    ACCESS  read-only
    STATUS  mandatory
    DESCRIPTION
        "Each entry contains the address of a management
         station."
    INDEX    { trapDestination }
    ::= { trapDestinationTable 1 }

TrapDestinationEntry ::= SEQUENCE {
    trapDestination
    NetworkAddress
}

trapDestination OBJECT-TYPE
    SYNTAX  NetworkAddress
    ACCESS  read-only
    STATUS  mandatory
    DESCRIPTION
        "Address to which the agent sends traps."
    ::= { trapDestinationEntry 1 }

END
